/* a comment */
// som more

module test1 {

  namespace "http://mynamespace.com/test1";
  prefix pfx;

  /* Linkage stmts */

  import interfaces { // shud come b4 revision
     prefix if;
  }
  include "as";

  /* Meta stmts */
  organization "ani.com";

  description "hello peg";

  /* Revisions */

  revision 2012-06-15 {
     description "rev" + "higher thn " + "nex one";
  }

  revision 2012-05-30 {
     description "shud come after prev"
    + "due to chrono chk";
  }

  /* Body stmts */
  container c1 {
     leaf l1 {
        type t1;
        tailf:info "leaf info";
        description "leaf desc";
     }
  }
}
